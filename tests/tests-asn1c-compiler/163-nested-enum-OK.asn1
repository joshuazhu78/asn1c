-- OK: Everything is fine

-- iso.org.dod.internet.private.enterprise (1.3.6.1.4.1)
-- .spelio.software.asn1c.test (9363.1.5.1)
-- .163

ModuleTestConstraints1
	{ iso org(3) dod(6) internet (1) private(4) enterprise(1)
		spelio(9363) software(1) asn1c(5) test(1) 163 }
	DEFINITIONS ::=
BEGIN

    Item2 ::= SEQUENCE {
        ie Item1,
        ...
    }

    Item1 ::= ENUMERATED {
        one,
        two,
        three,
        four,
        ...,
        five,
        six,
        seven
    }

    Item3 ::= CHOICE {
        ch1 Item2,
        ...,
        ch2 Item1
    }

    Item41 ::= SEQUENCE {
        en ENUMERATED {true, false, ..., accept, decline} OPTIONAL,
        ...
    }

    Item42 ::= CHOICE {
        ...,
        en ENUMERATED {true, false, ..., accept, decline}
    }

END
