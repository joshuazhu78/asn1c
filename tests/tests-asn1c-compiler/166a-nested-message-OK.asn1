-- OK: Everything is fine

-- iso.org.dod.internet.private.enterprise (1.3.6.1.4.1)
-- .spelio.software.asn1c.test (9363.1.5.1)
-- .166

ModuleTestClass
	{ iso org(3) dod(6) internet(1) private(4) enterprise(1)
		spelio(9363) software(1) asn1c(5) test(1) 166 }
	DEFINITIONS ::=
BEGIN

   SomeList ::= SEQUENCE (SIZE (1..20)) OF
   	SEQUENCE {
   		iECriticality			Criticality,
   		iE-ID					CodeID,
   		typeOfError				ENUMERATED{fatal, ...},
   		iE-Extensions			Response-Container { {SomeList-ExtIEs} } OPTIONAL,
   		...
   }

   SomeList-ExtIEs IE-DEFINITION ::= {
   	...
   }

   IE-DEFINITION ::= CLASS {
       &id             CodeID                  UNIQUE,
       &criticality    Criticality,
       &Value,
       &presence       Presence
   }
   WITH SYNTAX {
       ID             &id
       CRITICALITY     &criticality
       TYPE            &Value
       PRESENCE        &presence
   }

   Response-Container {IE-DEFINITION : IEsSetParam} ::= SEQUENCE (SIZE (0..16)) OF IE-Field {{IEsSetParam}}

   IE-Field {IE-DEFINITION : IEsSetParam} ::= SEQUENCE {
       id             IE-DEFINITION.&id              ({IEsSetParam}),
       criticality     IE-DEFINITION.&criticality      ({IEsSetParam}{@id}),
       value           IE-DEFINITION.&Value            ({IEsSetParam}{@id})
   }

    CodeID ::= INTEGER (0..128, ...)

    Criticality ::= ENUMERATED {
        high,
        low,
         ...
    }

    Presence ::= ENUMERATED {
        optional,
        mandatory,
         ...
    }

    id-operator1        CodeID ::= 1
    id-operator2        CodeID ::= 2

END
