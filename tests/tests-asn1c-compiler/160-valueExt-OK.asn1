-- OK: Everything is fine

-- iso.org.dod.internet.private.enterprise (1.3.6.1.4.1)
-- .spelio.software.asn1c.test (9363.1.5.1)
-- .160

ModuleTestConstraints1
	{ iso org(3) dod(6) internet (1) private(4) enterprise(1)
		spelio(9363) software(1) asn1c(5) test(1) 160 }
	DEFINITIONS ::=
BEGIN

    T2 ::= SEQUENCE {
        item T1
    }

    T1 ::= SEQUENCE {
        element-List		SEQUENCE (SIZE(1..16, ...)) OF ConstrainedString OPTIONAL,
        interval            LongerInterval,
        ...,
        cs                  ConstrainedString
    }

    ConstrainedString  ::= PrintableString(SIZE(1..150, ...))

    LongerInterval ::= INTEGER (-55..68719476735, ...)

END
