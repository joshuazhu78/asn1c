-- OK: Everything is fine

-- iso.org.dod.internet.private.enterprise (1.3.6.1.4.1)
-- .spelio.software.asn1c.test (9363.1.5.1)
-- .159

ModuleTestConstraints1
	{ iso org(3) dod(6) internet (1) private(4) enterprise(1)
		spelio(9363) software(1) asn1c(5) test(1) 159 }
	DEFINITIONS ::=
BEGIN

    PDU ::= SEQUENCE{
        element-List		SEQUENCE (SIZE(1..int123456)) OF ConstrainedString OPTIONAL,
        constrainedString  PrintableString(SIZE(1..150,...)) OPTIONAL,
        id BIT STRING (SIZE(22..32)) OPTIONAL,
        interval INTEGER (-100..int123456),
        other-ID OtherIdentity OPTIONAL,
        ...
    }

    ConstrainedString ::= PrintableString(SIZE(1..1000,...))

    OtherIdentity ::= OCTET STRING (SIZE(3))

	int123456 INTEGER ::= 123456

END
