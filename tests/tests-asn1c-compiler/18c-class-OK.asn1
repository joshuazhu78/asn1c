-- OK: Everything is fine

-- iso.org.dod.internet.private.enterprise (1.3.6.1.4.1)
-- .spelio.software.asn1c.test (9363.1.5.1)
-- .18

-- This definition doesn't contain unique flag in CLASS definition, so VALUE SET
-- should be represented with a CHOICE in natural ordering, not canonical ordering

ModuleTestClass
	{ iso org(3) dod(6) internet(1) private(4) enterprise(1)
		spelio(9363) software(1) asn1c(5) test(1) 18 }
	DEFINITIONS ::=
BEGIN

    Functions FUNCTION ::= {
        {CODE id-valueSet1,    ARGUMENT Type1,  PRESENCE mandatory,  CRITICALITY high} |
        {CODE id-valueSet2,    ARGUMENT Type2,  PRESENCE optional,   CRITICALITY low} | operator3
    }

	operator1 FUNCTION ::= {
		CODE            id-operator1,
		ARGUMENT        Type1,
		PRESENCE        mandatory,
		CRITICALITY     high
	}

	operator2 FUNCTION ::= {
   		CODE            id-operator2,
		ARGUMENT        Type2,
		PRESENCE        optional,
   		CRITICALITY     low
	}

    operator3 FUNCTION ::= {
        CODE            id-operator3,
        ARGUMENT        Type3,
        PRESENCE        optional,
        CRITICALITY     low
    }

    Type1 ::= SEQUENCE{
        se1 REAL,
        se2 OCTET STRING OPTIONAL,
        ...
    }

    Type2 ::= CHOICE {
        ch1 INTEGER,
        ch2 BIT STRING,
        ...
    }

    Type3 ::= OCTET STRING

	FUNCTION ::= CLASS {
		&code			CodeID,
		&ArgType,
		&presence       Presence    OPTIONAL,
		&criticality    Criticality
	}

	WITH SYNTAX {
		CODE            &code,
		ARGUMENT        &ArgType,
		PRESENCE        &presence,
		CRITICALITY     &criticality
	}

    CodeID ::= INTEGER (0..128, ...)

    Criticality ::= ENUMERATED {
        high,
        low,
         ...
    }

    Presence ::= ENUMERATED {
        optional,
        mandatory,
         ...
    }

    id-operator1        CodeID ::= 1
    id-operator2        CodeID ::= 2
    id-operator2        CodeID ::= 3
    id-valueSet1        CodeID ::= 21
    id-valueSet2        CodeID ::= 22

END
