-- OK: Everything is fine

-- iso.org.dod.internet.private.enterprise (1.3.6.1.4.1)
-- .spelio.software.asn1c.test (9363.1.5.1)
-- .164

ModuleLAPStorage
	{ iso org(3) dod(6) internet (1) private(4) enterprise(1)
		spelio(9363) software(1) asn1c(5) test(1) 164 }
	DEFINITIONS EXTENSIBILITY IMPLIED ::=
BEGIN

	Reference-structure ::= Reference-Structure

	Reference-Structure ::= SEQUENCE {
		list1		SEQUENCE SIZE(0..MAX) OF INTEGER(1..32,...),
		item	    BOOLEAN,
		...,
		list2		SEQUENCE SIZE(0..MAX) OF PrintableString
	}

	LogLine ::= SEQUENCE {
        ie  Reference-structure,
        ...
	}

END
