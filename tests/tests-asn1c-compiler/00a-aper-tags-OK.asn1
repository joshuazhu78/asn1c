-- OK: Everything is fine

-- iso.org.dod.internet.private.enterprise (1.3.6.1.4.1)
-- .spelio.software.asn1c.test (9363.1.5.1)
-- .0

ModuleTestConstraints1
	{ iso org(3) dod(6) internet (1) private(4) enterprise(1)
		spelio(9363) software(1) asn1c(5) test(1) 0 }
	DEFINITIONS ::=
BEGIN

    Some-List ::= SEQUENCE{
        element-List		SEQUENCE (SIZE(1..int123456)) OF ConstrainedString OPTIONAL,
        ...
    }

    Some-ID ::= BIT STRING (SIZE(22..32))

    Some-Identity ::= OCTET STRING (SIZE(4))

    ConstrainedString  ::= PrintableString(SIZE(1..150,...))

	int123456 INTEGER ::= 123456

	Interval ::= INTEGER (-100..int123456)

    LongerInterval ::= INTEGER (-55..68719476735)

END
